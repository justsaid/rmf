# Specification: Specification Document
- Description: Requirements Document

## INF-1 (Requirement Type)
Rohentwurf der Reporting Anfordrungen
- Rating: 0

### REQ-1: Link Visualisierung (Requirement Type)
Visualisierung der Abhängigkeiten von Anforderungen
- Rating: 230

### REQ-2: Weitere Darstellungsmittel (Requirement Type)
Darstellungsmittel, wie z.B. Charts, Tabellen, Präsentationen usw. für die Abbildung von ausgewählten Elemente
- Rating: 200

### REQ-3: Einfaches Drucken (Requirement Type)
Direkt aus ProR drucken, ohne die Anforderungen explizit in ein Druckformat zu überführen
- Rating: 110

### REQ-4: Nutzergruppen spezifisch (Requirement Type)
Für eine bestimmte Nutzergruppe eine speziell abgestimmten Bericht generieren
- Rating: 205

### REQ-5: Analysemodelle (Requirement Type)
Anforderungen einfach in Analysemodelle wie z.B. SysML ... überführen
- Rating: 150

### REQ-6: Wiederverwendbarkeit (Requirement Type)
Darstellung bzw. Berichte sollen wie sie zu sehen sind gesichert und weiter verarbeitet werden können
- Rating: 111

### REQ-6: Layout Customizing (Requirement Type)
Ein Nutzer soll individuell das Layout des Ausgabeformat festlegen können
- Rating: 220
- Status: Accept

### REQ-7: Templates (Requirement Type)
Templates als Vorlage für die Darstellung von Berichten
- Rating: 231
- links to -> INF-1

### REQ-8: Export Funktionen (Requirement Type)
Export Möglichkeiten in verschiedenen Formate, wie z.B. PDF, Excel, Word ...
- Rating: 240
- links to -> INF-1

## Req1 (Req_with_Prio)
- Priority: 5

## Req2 (Req_with_Prio)
- Priority: 3

## R13 (Requirement Type)
