# Specification: Specification Document
- Description: Requirements Document

## INF-1 (Requirement Type)
Rohentwurf der Reporting Anfordrungen

#### REQ-1: Link Visualisierung (Requirement Type)
Visualisierung der Abhängigkeiten von Anforderungen

#### REQ-2: Weitere Darstellungsmittel (Requirement Type)
Darstellungsmittel, wie z.B. Charts, Tabellen, Präsentationen usw. für die Abbildung von ausgewählten Elemente

#### REQ-3: Einfaches Drucken (Requirement Type)
Direkt aus ProR drucken, ohne die Anforderungen explizit in ein Druckformat zu überführen

#### REQ-4: Nutzergruppen spezifisch (Requirement Type)
Für eine bestimmte Nutzergruppe eine speziell abgestimmten Bericht generieren

#### REQ-5: Analysemodelle (Requirement Type)
Anforderungen einfach in Analysemodelle wie z.B. SysML ... überführen

#### REQ-6: Wiederverwendbarkeit (Requirement Type)
Darstellung bzw. Berichte sollen wie sie zu sehen sind gesichert und weiter verarbeitet werden können

#### REQ-6: Layout Customizing (Requirement Type)
Ein Nutzer soll individuell das Layout des Ausgabeformat festlegen können

#### REQ-7: Templates (Requirement Type)
Templates als Vorlage für die Darstellung von Berichten

#### REQ-8: Export Funktionen (Requirement Type)
Export Möglichkeiten in verschiedenen Formate, wie z.B. PDF, Excel, Word ...

## R2

## fdsa (Requirement Type)
